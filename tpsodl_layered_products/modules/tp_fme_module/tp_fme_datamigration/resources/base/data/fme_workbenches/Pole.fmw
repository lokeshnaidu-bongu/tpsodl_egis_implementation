FME workspace Pole.fmw

Parameters:
- SourceDataset_SHAPEFILE_4 =

Readers:
- SHAPEFILE_1: SHAPEFILE from $(SourceDataset_SHAPEFILE_4)

Writers:
- SWORLDSWAF_1: SWORLDSWAF in TPSODL-UTM-45N_MM

Pole (reader SHAPEFILE_1)
    attributes: Pl_No varchar(254), Volt_Class varchar(254), Str_Typ varchar(254), Insl_o_EHT varchar(254), Insl_O_HT varchar(254), No_EHT_Ckt long, No_HT_Ckt long, No_LT_Ckt long, No_Stay long, No_Stud long, Cut_Point varchar(254), Nom_Volt varchar(254), Couping varchar(254), Earthing varchar(254), Extension varchar(254), LA_Provd varchar(254), Jmpr_Conct varchar(254), Remark varchar(254), Rd_Cr_Grd varchar(254), Shared varchar(254), St_Lgt_Typ varchar(254), PSS_Code varchar(254), No_Brnch varchar(254), Feed_Nm varchar(254), Sub_Typ varchar(254), No_Tv_Tel varchar(254), No_St_Lgt long, Comp_Sts varchar(254), No_Srv varchar(254), GIS_ID varchar(254),
      Pl_Height varchar(254), Pole_Typ varchar(254), Danger_B_S varchar(254), Anti_Clm_D varchar(254), Pole_Cond varchar(254), Dimensions varchar(254), Owner_Name varchar(254), Owner_Type varchar(254), Status varchar(254), Ground_Cle varchar(254), Brnch_Sts varchar(254), Comp_Typ varchar(254), DTR_Code varchar(254), Cab_Raisin varchar(254), St_Lgt_Sts varchar(254), Frame_Type varchar(254), Feed_Code varchar(254), Lt_Ckt_No varchar(254), Cross_Arms varchar(254), Insl_O_LT varchar(254), Insl_Mat varchar(254), Pl_Mat varchar(254), EarthingCo varchar(254), SafeCleare varchar(254), Un_Migr_ID varchar(254), Any_ot_Cab varchar(254), GSS_Code varchar(254), Geo_Div_Na varchar(50), City varchar(50), Geo_Div_Co double,
      Geo_Cir_Co double, Insulators varchar(25), Geo_Sec_Co varchar(12), Geo_Sub_Di varchar(25), Pole_Struc varchar(50), No_of_Ot_C varchar(12), Usage varchar(50), DTR_Name varchar(50), F_L_Sea double, Geo_C_Name varchar(50)
    -> CoordinateSystemSetter
CoordinateSystemSetter
    COORDSYS = TPSODL-UTM-45N_MM
    -> Scaler
Scaler
    RASTER_SCALING = Extents
    SCALE_ORIGIN = 0,0
    TEXT_LOC_ONLY = Location and Size
    XSCALE = 1000
    YSCALE = 1000
    ZSCALE = 1
    SCALED -> GeometryPropertySetter
GeometryPropertySetter
    GEOM_NAME_FIELD = location
    OVERWRITE_CHOICE = Yes
    SETTYPE_PARAM = Geometry Name
    SET -> AttributeCreator
AttributeCreator
    ATTR_TABLE = SET_TO fme_db_operation = INSERT
    -> AttributeRemover
AttributeRemover
    REMOVE_ATTRS = Any_ot_Cab,Pl_Height,Insulators,No_of_Ot_C,F_L_Sea,Geo_C_Name,Geo_Cir_Co,Geo_Div_Co,Geo_Div_Na,Geo_Sec_Co,Geo_Sub_Di
    -> ed_pole (writer SWORLDSWAF_1)
ed_pole (writer SWORLDSWAF_1)
    attributes: asset_id char(37), tp_no_of_ehv_circuits char(50), material char(50), tp_no_of_lv_circuits char(50), tp_ehv_insulator_type char(50), usage char(50), tp_dtr_name char(50), tp_circle_name char(50), ed_pole_structure char(50), tp_sub_div_code char(50), tp_section_code char(50), class char(8), frame_type char(21), height char(9), id int, number char(21), owner_name char(121), owner_type char(20), remarks char(65535), status char(18), strength char(10), tp_anti_climbing_device char(8), tp_branching_status char(8), tp_cable_raising_term char(8), tp_circle_code char(50), tp_city char(50), tp_clearance_from_nearest_house char(8), tp_composite_status char(8), tp_composite_type char(14), tp_condition_of_pole char(16),
      tp_couping char(8), tp_cross_arm char(34), tp_cut_point char(8), tp_danger_board_status char(8), tp_dimensions char(8), tp_division_code char(50), tp_division_name char(50), tp_dtr_code char(65), tp_earthing char(8), tp_earthing_condition char(16), tp_extension char(33), tp_feeder_code char(65), tp_feeder_name char(65), tp_ground_clearance char(8), tp_gss_code char(64), tp_hv_insulator_type char(26), tp_insulator_material char(18), tp_jumper_connected char(65), tp_la_provided char(8), tp_lt_ckt_number char(65), tp_lv_insulator_type char(26), tp_migration_unique_id char(33), tp_mv_insulator_type char(26), tp_network_type char(11), tp_no_of_branches int, tp_no_of_hv_circuits int, tp_no_of_mv_circuits int, tp_no_of_service_lines int, tp_no_of_stay_wires int, tp_no_of_street_light int,
      tp_no_of_stud_poles int, tp_no_of_tv_tel char(65), tp_nominal_voltage char(11), tp_pss_code char(65), tp_road_cross_guarding char(8), tp_shared char(8), tp_street_light_status char(8), tp_street_light_type char(22), tp_structure_type char(14), tp_sub_type char(65), treatment char(18), type char(21)
