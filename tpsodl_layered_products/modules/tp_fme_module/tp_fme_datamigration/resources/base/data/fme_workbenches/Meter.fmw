FME workspace Meter.fmw

Parameters:
- SourceDataset_SHAPEFILE =

Readers:
- SHAPEFILE_1: SHAPEFILE from $(SourceDataset_SHAPEFILE)

Writers:
- SWORLDSWAF_1: SWORLDSWAF in TPSODL-UTM-45N_MM

Meter (reader SHAPEFILE_1)
    attributes: AMR_Instld varchar(12), Comu_Port varchar(32), DisplyCond varchar(32), Function varchar(32), Lf_Cyl_Sts varchar(32), Mtr_Box varchar(32), Volt_Cls varchar(12), Owner_Name varchar(32), Owner_Typ varchar(32), Phase varchar(6), Mtr_Cls varchar(32), Remarks varchar(254), Spce_Modem varchar(12), Feed_Nm varchar(32), Feed_Code varchar(10), Pole_No varchar(12), PSS_Code varchar(32), GIS_ID varchar(32), DT_Code varchar(12), Mechanism varchar(25), Nominal_Vo varchar(20), Meter_Seri varchar(30), Manufactur varchar(50), Date_Manuf varchar(20), PT_Ratio varchar(20), CT_Ratio varchar(20), No_of_Digi varchar(10), Total_MF varchar(20), Commun_Typ varchar(20), AMR_Mod_Sr long,
      Seal_Condi varchar(20), Seal_Type varchar(20), Meter_No varchar(12), Un_Migr_ID varchar(20), Power_Fact varchar(20)
    -> CoordinateSystemSetter
CoordinateSystemSetter
    COORDSYS = TPSODL-UTM-45N_MM
    -> Scaler
Scaler
    RASTER_SCALING = Extents
    SCALE_ORIGIN = 0,0
    TEXT_LOC_ONLY = Location and Size
    XSCALE = 1000
    YSCALE = 1000
    ZSCALE = 1
    SCALED -> GeometryPropertySetter
GeometryPropertySetter
    GEOM_NAME_FIELD = location
    OVERWRITE_CHOICE = Yes
    SETTYPE_PARAM = Geometry Name
    SET -> AttributeCreator
AttributeCreator
    ATTR_TABLE:
      SET_TO fme_db_operation = INSERT
      SET_TO tp_sub_division_code = Unknown
      SET_TO tp_sub_division_name
      SET_TO tp_ward_code
    -> AttributeRemover
AttributeRemover
    -> eo_meter (writer SWORLDSWAF_1)
eo_meter (writer SWORLDSWAF_1)
    attributes: date_manufactured date, device_type char(17), id int, mounting char(12), network_type char(11), nominal_voltage_pp char(11), number char(41), owner_name char(24), owner_type char(20), remarks char(65535), serial_number char(21), status char(18), tp_amr_installed char(8), tp_amr_model_ser_num char(33), tp_communication_port char(8), tp_communication_type char(9), tp_ct_ratio double, tp_display_condition char(16), tp_division_code char(8), tp_division_name char(15), tp_feeder_code char(65), tp_feeder_name char(65), tp_mechanism char(17), tp_meter_box char(14), tp_meter_height char(8), tp_migration_unique_id char(33), tp_mtr_fdr_dt_code char(33), tp_no_of_digits char(8), tp_phase char(15), tp_pole_number char(65),
      tp_power_factor double, tp_pss_code char(65), tp_pt_ratio double, tp_seal_condition char(16), tp_seal_type char(15), tp_space_for_modem_installation char(8), tp_sub_division_code char(8), tp_sub_division_name char(18), tp_sub_type char(14), tp_total_mf int, tp_type char(28), tp_ward_code char(8), tp_function char(15), tp_manufacturer char(39), tp_meter_location char(8)
