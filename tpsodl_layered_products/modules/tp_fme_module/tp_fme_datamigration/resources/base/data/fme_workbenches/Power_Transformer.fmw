FME workspace Power_Transformer.fmw

Parameters:
- SourceDataset_SHAPEFILE =

Readers:
- SHAPEFILE_1: SHAPEFILE from $(SourceDataset_SHAPEFILE)

Writers:
- SWORLDSWAF_1: SWORLDSWAF in TPSODL-UTM-45N_MM

DT (reader SHAPEFILE_1)
    attributes: Cool_Typ varchar(12), Type varchar(32), Ins_Typ varchar(32), Landmark varchar(32), Neu_Earth varchar(12), Star_Rat varchar(12), Sub_Type varchar(32), Phase varchar(6), Consum_Typ varchar(32), Feed_Name varchar(32), Meter_ID varchar(32), Metering varchar(12), Name varchar(250), DTR_Code varchar(12), Owner_Name varchar(32), Owner_Type varchar(32), Remarks varchar(254), Srvy_Remrk varchar(250), Vector_Grp varchar(12), GIS_ID varchar(32), Feed_Code varchar(12), Make varchar(50), Serial_No varchar(32), PSS_Code varchar(32), Prim_Nom_V varchar(20), Sec_Nom_Vt varchar(20), HVSideProt varchar(32), LVSideProt varchar(32), Sub_Mounti varchar(25), CondofTran varchar(20),
      Core varchar(32), Lifecycle varchar(25), No_of_Outg varchar(5), LA_Provide varchar(10), Un_Migr_ID varchar(20), Pole_No varchar(12), Specificat varchar(60), Vol_Clas_P varchar(10), Vol_Clas_S varchar(10), Opt_kVA varchar(20), Ngt_Status varchar(20), wkt_geom varchar(50), TotalLoss varchar(12), Total_Weig varchar(12), T_Rise_Oil double, Max_Tap double, Date_Manuf varchar(12), Impedance varchar(12), L_T_C__Ind varchar(12), Min_Tap varchar(12), T_C_N_Posi varchar(12), Min_Step varchar(12), No_of_Taps varchar(12), Max_Step varchar(12), Weight_Oil varchar(12), Prim_Curr varchar(12), No_Steps varchar(12), Core_Windi varchar(12), Oil_Qty varchar(12), Tap_Ch_Typ varchar(12),
      Adopt_Tap varchar(12), NG_Typ varchar(12), M_T_R_Wind varchar(12), T_C__P_Pos varchar(12), Dt_Of_Col varchar(12), NoLoadLoss varchar(12), G_Div_Name varchar(12), G_Divi_Cod varchar(12), Date_U_B_G varchar(12), Oil_P_Syst varchar(12), HVDS varchar(12), C_Oil_P_Sy varchar(12), Data_Cl_by varchar(12), Str_Mounti varchar(12), Time_d_col varchar(12), Mounting varchar(12), Geo_Cir_Na varchar(50), Sec_Curr varchar(12), CopperLoss double, Loss_50_ld double, W_Mat_Type varchar(12)
    -> CoordinateSystemSetter
CoordinateSystemSetter
    COORDSYS = TPSODL-UTM-45N_MM
    -> Scaler
Scaler
    RASTER_SCALING = Extents
    SCALE_ORIGIN = 0,0
    TEXT_LOC_ONLY = Location and Size
    XSCALE = 1000
    YSCALE = 1000
    ZSCALE = 1
    SCALED -> GeometryPropertySetter
GeometryPropertySetter
    GEOM_NAME_FIELD = location
    OVERWRITE_CHOICE = Yes
    SETTYPE_PARAM = Geometry Name
    SET -> AttributeCreator
AttributeCreator
    ATTR_TABLE = SET_TO fme_db_operation = INSERT
    -> AttributeRemover
AttributeRemover
    REMOVE_ATTRS = id
    -> eo_power_xfrmr (writer SWORLDSWAF_1)
    -> eo_power_xfrmr_inst (writer SWORLDSWAF_1)
eo_power_xfrmr_inst (writer SWORLDSWAF_1)
    attributes: alias char(121), bank_configuration char(34), banked_ind char(8), bay char(255), bay!int char(255), circuit_and_section!int char(255), circuit_source_stopper char(255), circuit_source_stopper!int char(255), comms_devices!int char(255), dac char(255), existing_phases char(255), feeding_section!int char(255), future_phases char(255), id int, installation_group char(255), installation_group!int char(255), kva_demand double, load_network_type char(11), load_nominal_voltage_pp char(11), location_description char(65535), location_description_id int, ltc_tap_position int, mounting char(12), name char(121), operational_group char(255), operational_group!int char(255), owner_name char(24), owner_type char(20), parallel_ind char(8), past_phases char(255),
      phase_context char(8), remarks char(65535), scada_type char(10), source_data char(65), source_id int, source_network_type char(11), source_nominal_voltage_pp char(11), special_loading char(30), status char(18), structure_mounting char(8), style_subcode char(37), total_apparent_power double, tp_address char(33), tp_average_pf double, tp_census_code char(33), tp_circle_code char(8), tp_circle_name char(12), tp_city char(8), tp_company_id char(33), tp_con_oil_pre_system char(8), tp_consumer_number char(41), tp_consumption_type char(8), tp_cyme_id char(33), tp_data_collected_in_gis char(33), tp_date_of_creation_in_gis date, tp_date_of_data_collection char(33), tp_date_of_filtration date, tp_date_of_last_updation_in_gis date, tp_date_updated_by_gis date, tp_division_code char(8),
      tp_division_name char(14), tp_dt_uq_nameplate_photo char(2), tp_dt_uq_structure_photo char(2), tp_failure_date_and_time date, tp_failure_reason char(33), tp_feeder_name char(65), tp_hvds char(8), tp_installation_type char(12), tp_locality char(33), tp_max_load_for_last_month int, tp_max_load_last_13_months int, tp_maximum_demand double, tp_metering_type char(12), tp_mig_phase char(65), tp_mig_spec char(255), tp_migration_unique_id char(33), tp_neutral_earthing_type char(14), tp_ngt char(8), tp_no_load_loss int, tp_number char(13), tp_oil_preserving_system char(8), tp_panchayat_code char(33), tp_panchayat_name char(129), tp_peak_load int, tp_pin_code int, tp_previous_installed_location char(33), tp_primary_side_protection char(65), tp_rated_sec_current double, tp_road_name char(33), tp_sap_functional_location char(33),
      tp_secondary_side_protection char(65), tp_section_code char(8), tp_section_name char(23), tp_sub_division_code char(8), tp_sub_division_name char(19), tp_sub_locality char(33), tp_sub_mounting char(19), tp_survey_remark char(65535), tp_time_of_data_collection char(33), tp_village_code char(33), tp_village_name char(129), tp_ward_code char(8)
eo_power_xfrmr (writer SWORLDSWAF_1)
    attributes: alias char(121), asset_id char(37), controller char(255), current_limiting_fuse_ind char(8), date_acquired date, date_manufactured date, device_type char(29), existing_phases char(255), future_phases char(255), id int, load_fuse_size char(10), load_fuse_type char(11), manufacturer char(39), past_phases char(255), remarks char(65535), remarks_id int, serial_number char(21), source_data char(65), source_fuse_size char(10), source_fuse_type char(11), source_id int, specification char(255), tap_position int, tp_adopted_tap int, tp_condition_of_xfrmr char(16), tp_cooling_type char(14), tp_core char(10), tp_date_of_last_maintenance date, tp_ea_equipment_id char(33), tp_landmark char(33),
      tp_load_tap_chng_indicator char(8), tp_manufacturer char(129), tp_maximum_demand double, tp_maximum_step int, tp_maximum_tap int, tp_mig_phase char(65), tp_mig_spec char(255), tp_migration_unique_id char(33), tp_minimum_step int, tp_minimum_tap int, tp_neutral_grounding_type char(14), tp_ngt_no int, tp_number_of_fans char(8), tp_number_of_steps char(8), tp_number_of_taps char(8), tp_oil_quantity double, tp_operating_rating_in_kva double, tp_percentage_loading double, tp_rated_capacity char(8), tp_rated_magnetizing_current double, tp_rated_primary_current double, tp_star_rating char(8), tp_sub_type char(20), tp_tap_changer_id char(33), tp_tap_changer_make char(39), tp_tap_changer_serial_number char(33), tp_tap_changer_type char(9), tp_tap_chng_nor_pos char(33), tp_tap_chng_prst_position char(65), tp_total_losses_at_50_per_load double,
      tp_total_weight int, tp_transport_weight int, tp_warranty_end_date date, tp_weight_core_and_winding double, tp_weight_of_oil int, tp_xfrmr_temp_rising_oil double, tp_xfrmr_temp_rising_wdg double
