FME workspace Measuring_Equipment.fmw

Parameters:
- SourceDataset_SHAPEFILE_3 =

Readers:
- SHAPEFILE_1: SHAPEFILE from $(SourceDataset_SHAPEFILE_3) in TPSODL-UTM-45N_M

Writers:
- SWORLDSWAF_1: SWORLDSWAF in TPSODL-UTM-45N_MM

Measuring_Equipment (reader SHAPEFILE_1)
    attributes: Owner_Name varchar(32), Owner_Typ varchar(32), Remarks varchar(254), Feed_Nm varchar(32), Feed_Code varchar(10), PSS_Code varchar(32), GIS_ID varchar(32), Device_Typ varchar(32), CT_No varchar(12), Sub_Typ varchar(32), Phase varchar(6), Accu_Cls varchar(32), Earthing varchar(12), Lf_Cyl_Sts varchar(32), Tot_Weight varchar(12), CT_Primary varchar(10), CT_Seconda varchar(10), Un_Migr_ID varchar(20), Pole_No varchar(12), PT_Primary varchar(25), PT_Second varchar(25), Specificat varchar(30), P_Volt_Cla varchar(20), S_Volt_Cla varchar(20), Mounting varchar(20), Manufactur varchar(30), Year_Manuf varchar(30), Burden varchar(20)
    -> CoordinateSystemSetter
CoordinateSystemSetter
    COORDSYS = TPSODL-UTM-45N_MM
    -> Scaler
Scaler
    RASTER_SCALING = Extents
    SCALE_ORIGIN = 0,0
    TEXT_LOC_ONLY = Location and Size
    XSCALE = 1000
    YSCALE = 1000
    ZSCALE = 1
    SCALED -> GeometryPropertySetter
GeometryPropertySetter
    GEOM_NAME_FIELD = source_location
    OVERWRITE_CHOICE = Yes
    SETTYPE_PARAM = Geometry Name
    SET -> AttributeCreator
AttributeCreator
    ATTR_TABLE = SET_TO fme_db_operation = INSERT
    -> AttributeRemover
AttributeRemover
    -> eo_measuring_eqpt_inst (writer SWORLDSWAF_1)
    -> eo_measuring_eqpt (writer SWORLDSWAF_1)
eo_measuring_eqpt (writer SWORLDSWAF_1)
    attributes: device_type char(20), id int, tp_mig_phase char(65), tp_mig_spec char(255), tp_migration_unique_id char(33), tp_number char(13), tp_sub_type char(16), existing_phases char(255)
eo_measuring_eqpt_inst (writer SWORLDSWAF_1)
    attributes: id int, mounting char(12), owner_name char(24), owner_type char(20), remarks char(65535), source_network_type char(11), load_network_type char(20), status char(18), tp_accuracy_class char(33), tp_burden double, tp_ct_primary double, tp_ct_secondary double, tp_data_collected_in_gis char(33), tp_earthing char(8), tp_feeder_code char(65), tp_feeder_name char(65), tp_mig_phase char(65), tp_mig_spec char(255), tp_migration_unique_id char(33), tp_pole_number char(65), tp_pss_code char(65), tp_pt_primary double, tp_pt_secondary double, phase_context char(8)
