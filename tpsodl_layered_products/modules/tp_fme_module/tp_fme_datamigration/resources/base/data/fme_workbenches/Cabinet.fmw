FME workspace Cabinet.fmw

Parameters:
- SourceDataset_SHAPEFILE =

Readers:
- SHAPEFILE_1: SHAPEFILE from $(SourceDataset_SHAPEFILE)

Writers:
- SWORLDSWAF_1: SWORLDSWAF in TPSODL-UTM-45N_MM

Cabinet (reader SHAPEFILE_1)
    attributes: Device_Typ varchar(50), Instal_Typ varchar(20), Nominal_Vo varchar(50), Status varchar(20), Sub_Mounti varchar(22), DTR_Code varchar(25), Un_Migr_ID varchar(30)
    -> CoordinateSystemSetter
CoordinateSystemSetter
    COORDSYS = TPSODL-UTM-45N_MM
    -> Scaler
Scaler
    RASTER_SCALING = Extents
    SCALE_ORIGIN = 0,0
    TEXT_LOC_ONLY = Location and Size
    XSCALE = 1000
    YSCALE = 1000
    ZSCALE = 1
    SCALED -> GeometryPropertySetter
GeometryPropertySetter
    GEOM_NAME_FIELD = extent
    OVERWRITE_CHOICE = Yes
    SETTYPE_PARAM = Geometry Name
    SET -> AttributeCreator
AttributeCreator
    ATTR_TABLE = SET_TO fme_db_operation = INSERT
    -> AttributeRemover
AttributeRemover
    REMOVE_ATTRS = DTR_Code
    -> ed_cabinet (writer SWORLDSWAF_1)
ed_cabinet (writer SWORLDSWAF_1)
    attributes: id int, tp_device_type char(30), tp_network_type char(11), tp_nominal_voltage char(11), owner_name char(121), owner_type char(20), manufacturer char(39), rated_voltage char(8), tp_date_manufactured date, tp_migration_unique_id char(33), type char(29), status char(18), tp_sub_mounting char(19), tp_installation_type char(12)
