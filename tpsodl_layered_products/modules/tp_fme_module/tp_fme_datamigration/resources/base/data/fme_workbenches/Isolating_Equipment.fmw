FME workspace Isolating_Equipment.fmw

Parameters:
- SourceDataset_SHAPEFILE =

Readers:
- SHAPEFILE_1: SHAPEFILE from $(SourceDataset_SHAPEFILE) in TPSODL-UTM-45N_M

Writers:
- SWORLDSWAF_1: SWORLDSWAF in TPSODL-UTM-45N_MM

Isolating_Equipment (reader SHAPEFILE_1)
    attributes: Device_Typ varchar(32), Insl_Typ varchar(32), Mechanism varchar(64), Nrm_Sts varchar(12), Phase varchar(6), Aut_Recloe varchar(12), Bypass varchar(12), Lf_Cyl_Sts varchar(32), Feed_Nm varchar(32), Nomi_Volt varchar(12), Number varchar(12), Owner_Nm varchar(32), Owner_Typ varchar(32), Remark varchar(254), Sub_Typ varchar(32), PSS_Code varchar(32), GIS_ID varchar(32), Pole_No varchar(32), Feed_Code varchar(12), DTR_Code varchar(12), Circuitnum varchar(20), Un_Migr_ID varchar(20), Volt_Class varchar(10), Mounting varchar(30), Specificat varchar(50)
    -> CoordinateSystemSetter
CoordinateSystemSetter
    COORDSYS = TPSODL-UTM-45N_MM
    -> Scaler
Scaler
    RASTER_SCALING = Extents
    SCALE_ORIGIN = 0,0
    TEXT_LOC_ONLY = Location and Size
    XSCALE = 1000
    YSCALE = 1000
    ZSCALE = 1
    SCALED -> GeometryPropertySetter
GeometryPropertySetter
    GEOM_NAME_FIELD = connector
    OVERWRITE_CHOICE = Yes
    SETTYPE_PARAM = Geometry Name
    SET -> AttributeCreator
AttributeCreator
    ATTR_TABLE = SET_TO fme_db_operation = INSERT
    -> AttributeRemover
AttributeRemover
    -> eo_isolating_eqpt (writer SWORLDSWAF_1)
    -> eo_isolating_eqpt_inst (writer SWORLDSWAF_1)
eo_isolating_eqpt (writer SWORLDSWAF_1)
    attributes: id int, device_type char(18), remarks char(65535), tp_mechanism char(17), tp_migration_unique_id char(33), tp_mig_phase char(65), tp_mig_spec char(255), existing_phases char(255), specification char(255), tp_sub_type char(30)
eo_isolating_eqpt_inst (writer SWORLDSWAF_1)
    attributes: id int, mounting char(12), network_type char(11), nominal_voltage_pp char(11), owner_name char(24), owner_type char(20), remarks char(65535), status char(18), tp_bypass char(8), tp_mig_phase char(65), tp_mig_spec char(255), tp_migration_unique_id char(251), tp_number char(65), tp_previous_installed_location char(13), tp_survey_remark char(65535), tp_installation_type char(12), source_data char(65)
