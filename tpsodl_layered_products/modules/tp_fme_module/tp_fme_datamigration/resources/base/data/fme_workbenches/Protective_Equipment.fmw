FME workspace Protective_Equipment.fmw

Parameters:
- SourceDataset_SHAPEFILE_3 =

Readers:
- SHAPEFILE_1: SHAPEFILE from $(SourceDataset_SHAPEFILE_3) in TPSODL-UTM-45N_M

Writers:
- SWORLDSWAF_1: SWORLDSWAF in TPSODL-UTM-45N_MM

Protective_Equipment (reader SHAPEFILE_1)
    attributes: Device_Typ varchar(32), Earthing varchar(12), Material varchar(12), Phase varchar(6), Feed_Nm varchar(32), Lf_Cyl_Sts varchar(32), Mounting varchar(12), Netw_Typ varchar(12), Nomi_Volt varchar(12), Owner_Nm varchar(32), Owner_Typ varchar(32), Remarks varchar(254), GIS_ID varchar(32), Pole_No varchar(32), Connect_St varchar(30), PSS_Code varchar(32), DTR_Code varchar(12), Feed_Code varchar(12), Un_Migr_ID varchar(20), Specificat varchar(60)
    -> CoordinateSystemSetter
CoordinateSystemSetter
    COORDSYS = TPSODL-UTM-45N_MM
    -> Scaler
Scaler
    RASTER_SCALING = Extents
    SCALE_ORIGIN = 0,0
    TEXT_LOC_ONLY = Location and Size
    XSCALE = 1000
    YSCALE = 1000
    ZSCALE = 1
    SCALED -> GeometryPropertySetter
GeometryPropertySetter
    GEOM_NAME_FIELD = location
    OVERWRITE_CHOICE = Yes
    SETTYPE_PARAM = Geometry Name
    SET -> AttributeCreator
AttributeCreator
    ATTR_TABLE = SET_TO fme_db_operation = INSERT
    -> AttributeRemover
AttributeRemover
    REMOVE_ATTRS = Connect_St
    -> eo_protective_eqpt (writer SWORLDSWAF_1)
    -> eo_protective_eqpt_inst (writer SWORLDSWAF_1)
eo_protective_eqpt (writer SWORLDSWAF_1)
    attributes: device_type char(21), id int, tp_earthing char(8), tp_material char(27), tp_mig_phase char(65), tp_migration_unique_id char(33), tp_mig_spec char(255), existing_phases char(255)
eo_protective_eqpt_inst (writer SWORLDSWAF_1)
    attributes: id int, mounting char(12), network_type char(11), nominal_voltage_pp char(11), owner_name char(24), owner_type char(20), remarks char(65535), status char(18), tp_dtr_code char(65), tp_dtr_name char(65), tp_feeder_code char(65), tp_feeder_name char(65), tp_mig_phase char(65), tp_mig_spec char(255), tp_migration_unique_id char(33), tp_pole_number char(65), tp_pss_code char(65), tp_sub_mounting char(19)
