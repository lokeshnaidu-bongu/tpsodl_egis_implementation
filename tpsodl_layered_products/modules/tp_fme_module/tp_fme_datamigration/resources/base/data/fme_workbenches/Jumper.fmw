FME workspace Jumper.fmw

Parameters:
- SourceDataset_SHAPEFILE =

Readers:
- SHAPEFILE_1: SHAPEFILE from $(SourceDataset_SHAPEFILE)

Writers:
- SWORLDSWAF_1: SWORLDSWAF in TPSODL-UTM-45N_MM

Jumper (reader SHAPEFILE_1)
    attributes: Phase varchar(6), Material varchar(12), Mounting varchar(12), Owner_Name varchar(32), Owner_Type varchar(32), Remarks varchar(254), Size varchar(12), Type varchar(32), Usage varchar(32), Feed_Nm varchar(32), Lif_Cy_Sts varchar(32), Netw_Typ varchar(12), Nom_Volt varchar(12), Srvy_Remrk varchar(250), PSS_Code varchar(32), Feed_Code varchar(12), Specificat varchar(80), Un_Migr_ID varchar(20), Pole_No varchar(32), ttt double
    -> CoordinateSystemSetter
CoordinateSystemSetter
    COORDSYS = TPSODL-UTM-45N_MM
    -> Scaler
Scaler
    RASTER_SCALING = Extents
    SCALE_ORIGIN = 0,0
    TEXT_LOC_ONLY = Location and Size
    XSCALE = 1000
    YSCALE = 1000
    ZSCALE = 1
    SCALED -> GeometryPropertySetter
GeometryPropertySetter
    GEOM_NAME_FIELD = route
    OVERWRITE_CHOICE = Yes
    SETTYPE_PARAM = Geometry Name
    SET -> AttributeCreator
AttributeCreator
    ATTR_TABLE = SET_TO fme_db_operation = INSERT
    -> AttributeRemover
AttributeRemover
    REMOVE_ATTRS = Size,ttt
    -> eo_wire_segment_inst (writer SWORLDSWAF_1)
    -> eo_wire (writer SWORLDSWAF_1)
eo_wire (writer SWORLDSWAF_1)
    attributes: id int, tp_mig_spec char(255), tp_migration_unique_id char(33), tp_mig_phase char(65), existing_phases char(255), tp_material char(255)
eo_wire_segment_inst (writer SWORLDSWAF_1)
    attributes: id int, mounting char(12), network_type char(11), nominal_voltage_pp char(11), owner_name char(24), owner_type char(20), remarks char(65535), status char(18), tp_dtr_code char(65), tp_feeder_code char(65), tp_group_with char(65), tp_lt_ckt_number char(65), tp_mig_phase char(65), tp_mig_spec char(255), tp_migration_unique_id char(33), tp_number char(13), tp_pss_code char(65), tp_sag int, tp_start_pole char(33), tp_survey_remark char(65535), tp_type char(10), usage char(20), tp_end_pole char(33), tp_feeder_name char(65)
