FME workspace Cable.fmw

Parameters:
- SourceDataset_SHAPEFILE_3 =

Readers:
- SHAPEFILE_1: SHAPEFILE from $(SourceDataset_SHAPEFILE_3)

Writers:
- SWORLDSWAF_1: SWORLDSWAF in TPSODL-UTM-45N_MM

Cable (reader SHAPEFILE_1)
    attributes: Phase varchar(6), Material varchar(12), Mounting varchar(12), No_of_Core number(12,0), Owner_Name varchar(32), Owner_Type varchar(32), Remarks varchar(254), Size varchar(12), Usage varchar(32), Insulation varchar(50), Feed_Nm varchar(32), Nom_Volt varchar(12), Volt_Class varchar(12), Armoured varchar(12), Srvy_Remrk varchar(250), From_GisID varchar(32), To_GisID varchar(32), PSS_Code varchar(32), Connect_St varchar(30), Feed_Code varchar(12), DTR_Code varchar(12), LT_Ckt_No varchar(50), Specificat varchar(50), Un_Migr_ID varchar(20), mmc_id double
    -> CoordinateSystemSetter
CoordinateSystemSetter
    COORDSYS = TPSODL-UTM-45N_MM
    -> Scaler
Scaler
    RASTER_SCALING = Extents
    SCALE_ORIGIN = 0,0
    TEXT_LOC_ONLY = Location and Size
    XSCALE = 1000
    YSCALE = 1000
    ZSCALE = 1
    SCALED -> GeometryPropertySetter
GeometryPropertySetter
    GEOM_NAME_FIELD = route
    OVERWRITE_CHOICE = Yes
    SETTYPE_PARAM = Geometry Name
    SET -> AttributeCreator
AttributeCreator
    ATTR_TABLE = SET_TO fme_db_operation = INSERT
    -> AttributeRemover
AttributeRemover
    REMOVE_ATTRS = Armoured,Size,mmc_id,Material
    -> eo_cable_segment_inst (writer SWORLDSWAF_1)
    -> eo_cable (writer SWORLDSWAF_1)
eo_cable (writer SWORLDSWAF_1)
    attributes: id int, tp_insulation_type char(11), tp_migration_unique_id char(33), tp_mig_phase char(65), tp_mig_spec char(255), existing_phases char(255)
eo_cable_segment_inst (writer SWORLDSWAF_1)
    attributes: tp_end_pole char(33), id int, mounting char(12), network_type char(11), nominal_voltage_pp char(11), owner_name char(24), owner_type char(20), remarks char(65535), status char(18), tp_dtr_code char(65), tp_feeder_code char(65), tp_feeder_name char(65), tp_lt_ckt_number char(65), tp_mig_phase char(65), tp_mig_spec char(255), tp_migration_unique_id char(33), tp_pss_code char(65), tp_start_pole char(33), tp_survey_remark char(65535), usage char(20), tp_number_of_cores char(8)
